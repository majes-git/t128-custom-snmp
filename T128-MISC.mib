-- Copyright (c) Juniper Networks, Inc. 2022. All rights reserved.
T128-MISC-MIB DEFINITIONS ::= BEGIN

--
-- Defines objects for additional statistics from the 128T Networking Platform
--

IMPORTS
    MODULE-IDENTITY, OBJECT-TYPE, IpAddress
        FROM SNMPv2-SMI

    DisplayString
        FROM SNMPv2-TC

    Integer32
        FROM SNMPv2-SMI

    t128PlatformSnmpMibs
        FROM T128-MIB
;


t128MiscellaneousMIB MODULE-IDENTITY
    LAST-UPDATED "202203310000Z"
    ORGANIZATION "www.128technology.com"
    CONTACT-INFO
        "Juniper Networks, Inc.
         Postal: 1133 Innovation Way
                 Sunnyvale, California, 94089
                 USA
         Support: https://support.juniper.net/support/
         web: www.juniper.net"
    DESCRIPTION
            "This MIB module defines objects that represent various statistics."

    -- revision history
    REVISION     "202203310000Z" -- Mar. 31, 2022
    DESCRIPTION  "Initial revision"

    ::= { t128PlatformSnmpMibs 128 }


t128MiscellaneousMIBSysinfo             OBJECT IDENTIFIER ::= { t128MiscellaneousMIB 1 }
t128MiscellaneousMIBNetworkInterfaces   OBJECT IDENTIFIER ::= { t128MiscellaneousMIB 10 }
t128MiscellaneousMIBPeerPaths           OBJECT IDENTIFIER ::= { t128MiscellaneousMIB 11 }
t128MiscellaneousMIBFib                 OBJECT IDENTIFIER ::= { t128MiscellaneousMIB 20 }
t128MiscellaneousMIBRib                 OBJECT IDENTIFIER ::= { t128MiscellaneousMIB 21 }
-- t128MiscellaneousMIBArp                 OBJECT IDENTIFIER ::= { t128MiscellaneousMIB 22 }

t128ArpTable OBJECT-TYPE
    SYNTAX  T128ArpTableEntry
    MAX-ACCESS  not-accessible
    STATUS  current
    DESCRIPTION
            "Show ARP table entries of an 128T/SSR router. (leant on RFC1213)"
    INDEX   { t128GlobalInterfaceId, t128IpAddress }
    ::= { t128MiscellaneousMIB 22 }

T128ArpTableEntry ::=
    SEQUENCE {
        t128GlobalInterfaceId
            Integer32,
        t128MacAddressHex
            OCTET STRING,
        t128IpAddress
            IpAddress,
        t128ArpEntryType
            Integer32,
        t128MacAddressString
            DisplayString
    }

t128GlobalInterfaceId OBJECT-TYPE
    SYNTAX      Integer32 (1..65535)
    MAX-ACCESS  not-accessible
    STATUS      current
    DESCRIPTION "Interface index"
    ::= { t128ArpTable 1 }

t128MacAddressHex OBJECT-TYPE
    SYNTAX      OCTET STRING
    MAX-ACCESS  read-only
    STATUS      current
    DESCRIPTION "MAC address as hex/octet string"
    ::= { t128ArpTable 2 }

t128IpAddress OBJECT-TYPE
    SYNTAX      IpAddress
    MAX-ACCESS  not-accessible
    STATUS      current
    DESCRIPTION "Target IP address"
    ::= { t128ArpTable 3 }

t128ArpEntryType OBJECT-TYPE
    SYNTAX      Integer32 (1..4)
    MAX-ACCESS  read-only
    STATUS      current
    DESCRIPTION "Type of the entry (dynamic, static, invalid)"
    ::= { t128ArpTable 4 }

t128MacAddressString OBJECT-TYPE
    SYNTAX      DisplayString (SIZE (0..17))
    MAX-ACCESS  read-only
    STATUS      current
    DESCRIPTION "MAC address as human readable string"
    ::= { t128ArpTable 5 }

t128NetworkInterfaceString OBJECT-TYPE
    SYNTAX      DisplayString (SIZE (0..255))
    MAX-ACCESS  read-only
    STATUS      current
    DESCRIPTION "Network interface name as human readable string"
    ::= { t128ArpTable 6 }

END
